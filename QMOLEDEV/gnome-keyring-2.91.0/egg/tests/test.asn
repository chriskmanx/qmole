TESTS { }

DEFINITIONS EXPLICIT TAGS ::=

BEGIN

TestInteger ::= INTEGER

TestBoolean ::= BOOLEAN

TestOctetString ::= OCTET STRING

TestGeneralized ::= GeneralizedTime

TestImplicit ::= [5] IMPLICIT OCTET STRING

TestExplicit ::= [5] EXPLICIT OCTET STRING

TestBitString ::= BIT STRING

TestIntegers ::= SEQUENCE {
	uint1                   INTEGER,
	uint2			INTEGER,
	uint3			INTEGER
}

TestData ::= SEQUENCE {
	data                    OCTET STRING
}

TestBooleanSeq ::= SEQUENCE {
	boolean                 BOOLEAN DEFAULT FALSE
}

TestOid ::= SEQUENCE {
	oid                     OBJECT IDENTIFIER
}

TestAnySeq ::= SEQUENCE {
	contents                ANY
}

END
