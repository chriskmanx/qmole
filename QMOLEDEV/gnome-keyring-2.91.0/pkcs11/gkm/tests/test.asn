TEST { }

DEFINITIONS EXPLICIT TAGS ::=

BEGIN

TestIntegers ::= SEQUENCE {
	mpi                     INTEGER
}

TestData ::= SEQUENCE {
	data			OCTET STRING,
	boolean                 BOOLEAN DEFAULT FALSE
}

END
