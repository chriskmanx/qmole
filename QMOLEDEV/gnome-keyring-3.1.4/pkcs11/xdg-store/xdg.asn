XDG { }

DEFINITIONS EXPLICIT TAGS ::=

BEGIN

-- This file contains definitions for keyring

TrustLevel ::= ENUMERATED {
	unknown              (0),
	untrusted            (1),
	trusted              (3),
	trustedAnchor        (4)
}

TrustAssertion ::= SEQUENCE {
	purpose                 OCTET STRING,
	level                   TrustLevel,
	peer                    OCTET STRING OPTIONAL,
	reserved                ANY OPTIONAL
}

TrustAssertions ::= SEQUENCE OF TrustAssertion

CertReference ::= SEQUENCE {
	serialNumber            INTEGER,
	issuer                  [1] ANY,
	subject                 [2] ANY OPTIONAL,
	reserved                [3] ANY OPTIONAL
}

TrustReference ::= CHOICE {
	certReference           [0] CertReference,
	certComplete            [1] ANY
}

trust-1 ::= SEQUENCE {
	reference               TrustReference,
	assertions              TrustAssertions,
	reserved                ANY OPTIONAL
}

END
